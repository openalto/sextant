module alto-auto-maps {
    yang-version 1;
    namespace "urn:alto:auto:maps";
    prefix "alto-auto-maps";

    import "ietf-yang-types" {
        prefix "ietf-types";
    }

    import "network-topology" {
        prefix "topology";
    }

    import "bgp-rib" {
        prefix "rib";
    }

    import "alto-basic-types" {
        prefix "alto-types";
    }

    organization "Yale University";

    contact "alto-dev@lists.opendaylight.org";

    revision "2015-01-05" {
        description "Initial revision of alto-auto-maps model";
    }

    typedef topology-type {
        type enumeration {
            enum openflow;
            enum bgp-ipv4;
            enum bgp-ls;
        }
    }

    // TODO: Augment to config-context of manual map
    list config-context {
        key "context-id";

        leaf "context-id" {
            type ietf-types:uuid;
            default "00000000-0000-0000-0000-000000000000";
        }

        list network-map-config {
            key "resource-id";

            leaf "resource-id" {
                mandatory true;
                type alto-types:resource-id;
            }

            choice params {
                case openflow {
                    container openflow-params {
                        leaf topology-id {
                            mandatory true;
                            type topology:topology-id;
                        }
                    }
                }
                case bgp {
                    container bgp-params {
                        list bgp-rib {
                            key rib-id;
                            leaf rib-id {
                                mandatory true;
                                type rib:rib-id;
                            }
                            leaf topology-id {
                                type topology:topology-id;
                            }
                            leaf bgp-ls {
                                type boolean;
                            }
                        }
                    }
                }
            }

            choice algorithm {
                case shortest-path-tree-cluster {
                    container spt-cluster-algorithm {
                        leaf spt-root {
                            mandatory true;
                            type topology:node-id;
                        }
                        leaf radix {
                            type int32;
                        }
                    }
                }
                case first-hop-cluster {
                    container first-hop-cluster-algorithm {
                        leaf inspect-igp {
                            type boolean;
                            default false;
                        }
                        leaf inspect-internal-link {
                            type boolean;
                            default true;
                        }
                    }
                }
            }
        }

        list cost-map-config {
            key "resource-id";

            leaf "resource-id" {
                mandatory true;
                type alto-types:resource-id;
            }

            leaf "dependent-network-map" {
                mandatory true;
                type alto-types:resource-id;
            }

            choice general-params {
                case bgp {
                    container bgp-params {
                        list alternative-bgp-rib {
                            key rib-id;
                            leaf rib-id {
                                mandatory true;
                                type rib:rib-id;
                            }
                            leaf topology-id {
                                type topology:topology-id;
                            }
                            leaf bgp-ls {
                                type boolean;
                            }
                        }
                    }
                }
            }

            list cost-type {
                uses alto-types:cost-type-data;
                key "cost-mode cost-metric";

                choice params {
                    // to be augmented
                }
            }
        }
    }
}
